import FreeCAD as App
import FreeCADGui as Gui

# Get the active document
doc = App.activeDocument()
if doc is None:
    App.Console.PrintError("Error: No active document.\n")
else:
    # Get the selected objects
    selection = Gui.Selection.getSelection()
    
    if len(selection) == 0:
        App.Console.PrintError("Please select a sketch, a face, or a closed sketch contour.\n")
    else:
        selected_obj = selection[0]
        
        # Check if it's a sketch, face, or closed contour
        if selected_obj.TypeId in ['Sketcher::SketchObject', 'Part::Feature', 'PartDesign::Feature']:
            # Check if the object is in a Body
            if hasattr(selected_obj, 'InList') and len(selected_obj.InList) > 0:
                parent = selected_obj.InList[0]
                if parent.TypeId == 'PartDesign::Body':
                    body = parent
                    
                    # Create the Pocket (Through All)
                    pocket = body.newObject('PartDesign::Pocket', 'Pocket')
                    pocket.Profile = selected_obj
                    pocket.Type = 1  # Through All
                    
                    # Recompute
                    doc.recompute()
                    
                    print("Through All Pocket created successfully")
                else:
                    App.Console.PrintError("The selected object must be in a Body.\n")
            else:
                App.Console.PrintError("The selected object must be in a Body.\n")
        else:
            App.Console.PrintError("Invalid selection. Please select a sketch, a face, or a closed sketch contour.\n")
