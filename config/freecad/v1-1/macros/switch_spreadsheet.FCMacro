import FreeCADGui as Gui

# Switch to SpreadsheetWorkbench Workbench
try:
    Gui.activateWorkbench("SpreadsheetWorkbench")
    print("Workbench changed to: SpreadsheetWorkbench")
except Exception as e:
    print("Error: " + str(e))
