import FreeCADGui as Gui

def change_to_assembly():
    """Change vers le Workbench Assembly."""
    try:
        Gui.activateWorkbench("AssemblyWorkbench")
        print("✅ Workbench changé en : Assembly")
    except Exception as e:
        print(f"⚠️ Erreur : {str(e)}")

change_to_assembly()
